// SysML v2 Model: StarForgeClicker
// Generated by SysML Web IDE
// 2026-10-20T20:46:47.080Z

package StarForgeClicker {
  private import ScalarValues;
  
  enum def UpgradeState {
    available;
    lowDust;
    locked;
  }
  
  enum def AchievementState {
    unlocked;
    hidden;
    closed;
  }
  
  part def Upgrade {
    attribute title : String;
    
    attribute baseCost : Natural;
    
    attribute costGrowth : Real;
  }
  
  part def GameModel {
    attribute dust : Real;
    
    attribute dustPerSec : Real;
    
    attribute level : Natural;
  }
  
  part def GameController {
    attribute tickMs : Natural;
  }
  
  part def SaveStorage {
    attribute autoSaveSeconds : Natural;
  }
  
  part def UserInterface;
  
  part def Player;
  
  part def StarForgeApp {
    connect ui to controller;
    connect controller to model;
    connect model to storage;
    
    part model : GameModel;
    
    part controller : GameController;
    
    part ui : UserInterface;
    
    part storage : SaveStorage;
  }
  
  part starForge : StarForgeApp;
  
  use case def ClickCore {
    subject app : StarForgeApp;
    
    actor player : Player;
  }
  
  use case def BuyUpgrades {
    subject app : StarForgeApp;
    
    actor player : Player;
  }
  
  use case def ViewAchievements {
    subject app : StarForgeApp;
    
    actor player : Player;
  }
  
  package Requirements {
    requirement def MemoryLimit {
      attribute maxMemoryMB : Natural;
    }
    
    requirement def TwoClicks {
      attribute maxClicks : Natural;
    }
    
    requirement def AutoSave {
      attribute saveSeconds : Natural;
    }
    
    requirement def PassiveTick;
    
    requirement def DarkSpaceStyle;
    
    requirement def LocalOnly;
    
    requirement 'REQ-PERF-001' memoryLimit : MemoryLimit;
    
    requirement 'REQ-FUNC-012' twoClicks : TwoClicks;
    
    requirement 'REQ-REL-001' autoSave : AutoSave;
    
    requirement 'REQ-FUNC-005' passiveTick : PassiveTick;
    
    requirement 'REQ-INT-001' darkSpaceStyle : DarkSpaceStyle;
    
    requirement 'REQ-CON-001' localOnly : LocalOnly;
  }
}
